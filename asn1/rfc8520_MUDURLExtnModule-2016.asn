MUDURLExtnModule-2016 { iso(1) identified-organization(3) dod(6)
                   internet(1) security(5) mechanisms(5) pkix(7)
                   id-mod(0) id-mod-mudURLExtn2016(88) }
       DEFINITIONS IMPLICIT TAGS ::= BEGIN

       -- EXPORTS ALL --

      IMPORTS

        -- RFC 5912
        EXTENSION
        FROM PKIX-CommonTypes-2009
             { iso(1) identified-organization(3) dod(6) internet(1)
               security(5) mechanisms(5) pkix(7) id-mod(0)
               id-mod-pkixCommon-02(57) }

        -- RFC 5912
        id-ct
        FROM PKIXCRMF-2009
             { iso(1) identified-organization(3) dod(6) internet(1)
               security(5)  mechanisms(5) pkix(7) id-mod(0)
               id-mod-crmf2005-02(55) }

        -- RFC 6268
        CONTENT-TYPE
        FROM CryptographicMessageSyntax-2010
          { iso(1) member-body(2) us(840) rsadsi(113549)
            pkcs(1) pkcs-9(9) smime(16) modules(0) id-mod-cms-2009(58) }

        -- RFC 5912
        id-pe, Name
        FROM PKIX1Explicit-2009
              { iso(1) identified-organization(3) dod(6) internet(1)
                security(5) mechanisms(5) pkix(7) id-mod(0)
                id-mod-pkix1-explicit-02(51) } ;

       --
       -- Certificate Extensions
       --

       MUDCertExtensions EXTENSION ::=
          { ext-MUDURL | ext-MUDsigner, ... }

       ext-MUDURL EXTENSION ::=






          { SYNTAX MUDURLSyntax IDENTIFIED BY id-pe-mud-url }

       id-pe-mud-url OBJECT IDENTIFIER ::= { id-pe 25 }

       MUDURLSyntax ::= IA5String

       ext-MUDsigner EXTENSION ::=
          { SYNTAX MUDsignerSyntax IDENTIFIED BY id-pe-mudsigner }

       id-pe-mudsigner OBJECT IDENTIFIER ::= { id-pe 30 }

       MUDsignerSyntax ::= Name

       --
       -- CMS Content Types
       --

       MUDContentTypes CONTENT-TYPE ::=
          { ct-mud, ... }

        ct-mud CONTENT-TYPE ::=
          { -- directly include the content
            IDENTIFIED BY id-ct-mudtype }
          -- The binary data that is in the form
          -- "application/mud+json" is directly encoded as the
          -- signed data.  No additional ASN.1 encoding is added.

       id-ct-mudtype OBJECT IDENTIFIER ::= { id-ct 41 }

       END
