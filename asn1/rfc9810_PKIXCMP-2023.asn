PKIXCMP-2023
       { iso(1) identified-organization(3) dod(6) internet(1)
       security(5) mechanisms(5) pkix(7) id-mod(0)
       id-mod-cmp2023-02(116) }
   DEFINITIONS EXPLICIT TAGS ::=
   BEGIN
   IMPORTS

   AttributeSet{}, SingleAttribute{}, Extensions{}, EXTENSION, ATTRIBUTE
   FROM PKIX-CommonTypes-2009
       {iso(1) identified-organization(3) dod(6) internet(1) security(5)
       mechanisms(5) pkix(7) id-mod(0) id-mod-pkixCommon-02(57)}

   AlgorithmIdentifier{}, SIGNATURE-ALGORITHM, ALGORITHM,
       DIGEST-ALGORITHM, MAC-ALGORITHM, KEY-DERIVATION
   FROM AlgorithmInformation-2009
       {iso(1) identified-organization(3) dod(6) internet(1) security(5)
       mechanisms(5) pkix(7) id-mod(0)
       id-mod-algorithmInformation-02(58)}

   Certificate, CertificateList, Time, id-kp
   FROM PKIX1Explicit-2009
       {iso(1) identified-organization(3) dod(6) internet(1) security(5)
       mechanisms(5) pkix(7) id-mod(0) id-mod-pkix1-explicit-02(51)}

   DistributionPointName, GeneralNames, GeneralName, KeyIdentifier
   FROM PKIX1Implicit-2009
       {iso(1) identified-organization(3) dod(6) internet(1) security(5)
       mechanisms(5) pkix(7) id-mod(0) id-mod-pkix1-implicit-02(59)}

   CertTemplate, PKIPublicationInfo, EncryptedKey, CertId,
       CertReqMessages, Controls, RegControlSet, id-regCtrl
   FROM PKIXCRMF-2009
       { iso(1) identified-organization(3) dod(6) internet(1)
       security(5) mechanisms(5) pkix(7) id-mod(0)
       id-mod-crmf2005-02(55) }
       -- The import of EncryptedKey is added due to the updates made
       -- in [RFC9480]. EncryptedValue does not need to be imported
       -- anymore and is therefore removed here.

   CertificationRequest
   FROM PKCS-10
       {iso(1) identified-organization(3) dod(6) internet(1) security(5)
       mechanisms(5) pkix(7) id-mod(0) id-mod-pkcs10-2009(69)}
   -- (specified in [RFC2986] with 1993 ASN.1 syntax and IMPLICIT
   -- tags).  Alternatively, implementers may directly include
   -- the syntax of [RFC2986] in this module.

   localKeyId
   FROM PKCS-9
       {iso(1) member-body(2) us(840) rsadsi(113549) pkcs(1) pkcs-9(9)
       modules(0) pkcs-9(1)}
       -- The import of localKeyId is added due to the updates made in
       -- [RFC9480]

   EnvelopedData, SignedData
   FROM CryptographicMessageSyntax-2010
       {iso(1) member-body(2) us(840) rsadsi(113549) pkcs(1) pkcs-9(9)
       smime(16) modules(0) id-mod-cms-2009(58)}
       -- The import of EnvelopedData and SignedData from [RFC6268] is
       -- added due to the updates made in CMP Updates [RFC9480]

   KEM-ALGORITHM
   FROM KEMAlgorithmInformation-2023  -- [RFC9629]
       { iso(1) identified-organization(3) dod(6) internet(1)
       security(5) mechanisms(5) pkix(7) id-mod(0)
       id-mod-kemAlgorithmInformation-2023(109) }
       -- The import of KEM-ALGORITHM was added due to the updates made
       -- in [RFC9810]
   ;

   -- History of the PKIXCMP ASN.1 modules
   -- [RFC2510]
   --    1988 Syntax, PKIXCMP, 1.3.6.1.5.5.7.0.9 (id-mod-cmp)
   --    Obsoleted by RFC 4210 PKIXCMP, 1.3.6.1.5.5.7.0.16
   --                                   (id-mod-cmp2000)
   -- [RFC4210]
   --    1988 Syntax, PKIXCMP, 1.3.6.1.5.5.7.0.16 (id-mod-cmp2000)
   --    Replaced by RFC 9480 PKIXCMP, 1.3.6.1.5.5.7.0.99
   --                                  (id-mod-cmp2021-88)
   -- [RFC5912]
   --    2002 Syntax, PKIXCMP-2009, 1.3.6.1.5.5.7.0.50
   --                               (id-mod-cmp2000-02)
   --    Replaced by RFC 9480 PKIXCMP-2021, 1.3.6.1.5.5.7.0.100
   --                                       (id-mod-cmp2021-02)
   -- [RFC9480]
   --    1988 Syntax, PKIXCMP, 1.3.6.1.5.5.7.0.99 (id-mod-cmp2021-88)
   --    2002 Syntax, PKIXCMP-2021, 1.3.6.1.5.5.7.0.100
   --                               (id-mod-cmp2021-02)
   --    Obsoleted by [RFC9810] PKIXCMP-2023, 1.3.6.1.5.5.7.0.116
   --                                         (id-mod-cmp2023-02)
   -- [RFC9810]
   --    2002 Syntax, PKIXCMP-2023, 1.3.6.1.5.5.7.0.116
   --                               (id-mod-cmp2023-02)


   -- The rest of the module contains locally defined OIDs and
   -- constructs:

   CMPCertificate ::= CHOICE { x509v3PKCert Certificate, ... }
   -- This syntax, while bits-on-the-wire compatible with the
   -- standard X.509 definition of "Certificate", allows the
   -- possibility of future certificate types (such as X.509
   -- attribute certificates, card-verifiable certificates, or other
   -- kinds of certificates) within this Certificate Management
   -- Protocol, should a need ever arise to support such generality.
   -- Those implementations that do not foresee a need to ever support
   -- other certificate types MAY, if they wish, comment out the
   -- above structure and "uncomment" the following one prior to
   -- compiling this ASN.1 module.  (Note that interoperability
   -- with implementations that don't do this will be unaffected by
   -- this change.)

   -- CMPCertificate ::= Certificate

   PKIMessage ::= SEQUENCE {
       header           PKIHeader,
       body             PKIBody,
       protection   [0] PKIProtection OPTIONAL,
       extraCerts   [1] SEQUENCE SIZE (1..MAX) OF CMPCertificate
                     OPTIONAL }

   PKIMessages ::= SEQUENCE SIZE (1..MAX) OF PKIMessage

   PKIHeader ::= SEQUENCE {
       pvno                INTEGER     { cmp1999(1), cmp2000(2),
                                         cmp2021(3) },
       sender              GeneralName,
       -- identifies the sender
       recipient           GeneralName,
       -- identifies the intended recipient
       messageTime     [0] GeneralizedTime         OPTIONAL,
       -- time of production of this message (used when sender
       -- believes that the transport will be "suitable", i.e.,
       -- that the time will still be meaningful upon receipt)
       protectionAlg   [1] AlgorithmIdentifier{ALGORITHM, {...}}
                               OPTIONAL,
       -- algorithm used for calculation of protection bits
       senderKID       [2] KeyIdentifier           OPTIONAL,
       recipKID        [3] KeyIdentifier           OPTIONAL,
       -- to identify specific keys used for protection
       transactionID   [4] OCTET STRING            OPTIONAL,
       -- identifies the transaction, i.e., this will be the same in
       -- corresponding request, response, certConf, and pkiconf
       -- messages
       senderNonce     [5] OCTET STRING            OPTIONAL,
       recipNonce      [6] OCTET STRING            OPTIONAL,
       -- nonces used to provide replay protection, senderNonce
       -- is inserted by the creator of this message; recipNonce
       -- is a nonce previously inserted in a related message by
       -- the intended recipient of this message.
       freeText        [7] PKIFreeText             OPTIONAL,
       -- this may be used to indicate context-specific instructions
       -- (this field is intended for human consumption)
       generalInfo     [8] SEQUENCE SIZE (1..MAX) OF
                           InfoTypeAndValue     OPTIONAL
       -- this may be used to convey context-specific information
       -- (this field is not primarily intended for human consumption)
   }

   PKIFreeText ::= SEQUENCE SIZE (1..MAX) OF UTF8String
       -- text encoded as UTF-8 string [RFC3629]

   PKIBody ::= CHOICE {       -- message-specific body elements
       ir       [0]  CertReqMessages,        --Initialization Request
       ip       [1]  CertRepMessage,         --Initialization Response
       cr       [2]  CertReqMessages,        --Certification Request
       cp       [3]  CertRepMessage,         --Certification Response
       p10cr    [4]  CertificationRequest,   --imported from [RFC2986]
       popdecc  [5]  POPODecKeyChallContent, --pop Challenge
       popdecr  [6]  POPODecKeyRespContent,  --pop Response
       kur      [7]  CertReqMessages,        --Key Update Request
       kup      [8]  CertRepMessage,         --Key Update Response
       krr      [9]  CertReqMessages,        --Key Recovery Request
       krp      [10] KeyRecRepContent,       --Key Recovery Response
       rr       [11] RevReqContent,          --Revocation Request
       rp       [12] RevRepContent,          --Revocation Response
       ccr      [13] CertReqMessages,        --Cross-Cert. Request
       ccp      [14] CertRepMessage,         --Cross-Cert. Response
       ckuann   [15] CAKeyUpdContent,        --CA Key Update Ann.
       cann     [16] CertAnnContent,         --Certificate Ann.
       rann     [17] RevAnnContent,          --Revocation Ann.
       crlann   [18] CRLAnnContent,          --CRL Announcement
       pkiconf  [19] PKIConfirmContent,      --Confirmation
       nested   [20] NestedMessageContent,   --Nested Message
       genm     [21] GenMsgContent,          --General Message
       genp     [22] GenRepContent,          --General Response
       error    [23] ErrorMsgContent,        --Error Message
       certConf [24] CertConfirmContent,     --Certificate Confirm
       pollReq  [25] PollReqContent,         --Polling Request
       pollRep  [26] PollRepContent          --Polling Response
   }

   PKIProtection ::= BIT STRING

   ProtectedPart ::= SEQUENCE {
       header    PKIHeader,
       body      PKIBody }

   id-PasswordBasedMac OBJECT IDENTIFIER ::= { iso(1) member-body(2)
       usa(840) nt(113533) nsn(7) algorithms(66) 13 }
   PBMParameter ::= SEQUENCE {
       salt                OCTET STRING,
       -- Note:  Implementations MAY wish to limit acceptable sizes
       -- of this string to values appropriate for their environment
       -- in order to reduce the risk of denial-of-service attacks.
       owf                 AlgorithmIdentifier{DIGEST-ALGORITHM, {...}},
       -- AlgId for the OWF
       iterationCount      INTEGER,
       -- number of times the OWF is applied
       -- Note:  Implementations MAY wish to limit acceptable sizes
       -- of this integer to values appropriate for their environment
       -- in order to reduce the risk of denial-of-service attacks.
       mac                 AlgorithmIdentifier{MAC-ALGORITHM, {...}}
       -- AlgId of the MAC algorithm
   }

   id-DHBasedMac OBJECT IDENTIFIER ::= { iso(1) member-body(2)
       usa(840) nt(113533) nsn(7) algorithms(66) 30 }
   DHBMParameter ::= SEQUENCE {
       owf                 AlgorithmIdentifier{DIGEST-ALGORITHM, {...}},
       -- AlgId for an OWF
       mac                 AlgorithmIdentifier{MAC-ALGORITHM, {...}}
       -- AlgId of the MAC algorithm
   }

   -- id-KemBasedMac and KemBMParameter were added in [RFC9810]

   id-KemBasedMac OBJECT IDENTIFIER ::= { iso(1) member-body(2)
       usa(840) nt(113533) nsn(7) algorithms(66) 16 }
   KemBMParameter ::= SEQUENCE {
       kdf              AlgorithmIdentifier{KEY-DERIVATION, {...}},
       -- AlgId of the Key Derivation Function algorithm
       kemContext   [0] OCTET STRING OPTIONAL,
       -- MAY contain additional algorithm-specific context information
       len              INTEGER (1..MAX),
       -- Defines the length of the keying material output of the KDF
       -- SHOULD be the maximum key length of the MAC function
       mac              AlgorithmIdentifier{MAC-ALGORITHM, {...}}
       -- AlgId of the MAC algorithm
   }

   PKIStatus ::= INTEGER {
       accepted               (0),
       -- you got exactly what you asked for
       grantedWithMods        (1),
       -- you got something like what you asked for; the
       -- requester is responsible for ascertaining the differences
       rejection              (2),
       -- you don't get it, more information elsewhere in the message
       waiting                (3),
       -- the request body part has not yet been processed; expect to
       -- hear more later (note: proper handling of this status
       -- response MAY use the polling req/rep PKIMessages specified
       -- in Section 5.3.22; alternatively, polling in the underlying
       -- transport layer MAY have some utility in this regard)
       revocationWarning      (4),
       -- this message contains a warning that a revocation is
       -- imminent
       revocationNotification (5),
       -- notification that a revocation has occurred
       keyUpdateWarning       (6)
       -- update already done for the oldCertId specified in
       -- CertReqMsg
   }

   PKIFailureInfo ::= BIT STRING {
   -- since we can fail in more than one way!
   -- More codes may be added in the future if/when required.
       badAlg              (0),
       -- unrecognized or unsupported algorithm identifier
       badMessageCheck     (1),
       -- integrity check failed (e.g., signature did not verify)
       badRequest          (2),
       -- transaction not permitted or supported
       badTime             (3),
       -- messageTime was not sufficiently close to the system time,
       -- as defined by local policy
       badCertId           (4),
       -- no certificate could be found matching the provided criteria
       badDataFormat       (5),
       -- the data submitted has the wrong format
       wrongAuthority      (6),
       -- the authority indicated in the request is different from the
       -- one creating the response token
       incorrectData       (7),
       -- the requester's data is incorrect (for notary services)
       missingTimeStamp    (8),
       -- when the timestamp is missing but should be there
       -- (by policy)
       badPOP              (9),
       -- the POP failed
       certRevoked         (10),
       -- the certificate has already been revoked
       certConfirmed       (11),
       -- the certificate has already been confirmed
       wrongIntegrity      (12),
       -- KEM ciphertext missing for MAC-based protection of response,
       -- or not valid integrity of message received (password based
       -- instead of signature or vice versa)
       badRecipientNonce   (13),
       -- not valid recipient nonce, either missing or wrong value
       timeNotAvailable    (14),
       -- the TSA's time source is not available
       unacceptedPolicy    (15),
       -- the requested TSA policy is not supported by the TSA
       unacceptedExtension (16),
       -- the requested extension is not supported by the TSA
       addInfoNotAvailable (17),
       -- the additional information requested could not be
       -- understood or is not available
       badSenderNonce      (18),
       -- not valid sender nonce, either missing or wrong size
       badCertTemplate     (19),
       -- not valid cert. template or missing mandatory information
       signerNotTrusted    (20),
       -- signer of the message unknown or not trusted
       transactionIdInUse  (21),
       -- the transaction identifier is already in use
       unsupportedVersion  (22),
       -- the version of the message is not supported
       notAuthorized       (23),
       -- the sender was not authorized to make the preceding
       -- request or perform the preceding action
       systemUnavail       (24),
       -- the request cannot be handled due to system unavailability
       systemFailure       (25),
       -- the request cannot be handled due to system failure
       duplicateCertReq    (26)
       -- certificate cannot be issued because a duplicate
       -- certificate already exists
   }

   PKIStatusInfo ::= SEQUENCE {
       status        PKIStatus,
       statusString  PKIFreeText     OPTIONAL,
       failInfo      PKIFailureInfo  OPTIONAL }

   OOBCert ::= CMPCertificate

   OOBCertHash ::= SEQUENCE {
       hashAlg     [0] AlgorithmIdentifier{DIGEST-ALGORITHM, {...}}
                           OPTIONAL,
       certId      [1] CertId                  OPTIONAL,
       hashVal         BIT STRING
       -- hashVal is calculated over the DER encoding of the
       -- self-signed certificate with the identifier certID.
   }

   POPODecKeyChallContent ::= SEQUENCE OF Challenge
   -- One Challenge per encryption or key agreement key certification
   -- request (in the same order as these requests appear in
   -- CertReqMessages).

   -- encryptedRand was added in [RFC9810]

   Challenge ::= SEQUENCE {
      owf                 AlgorithmIdentifier{DIGEST-ALGORITHM, {...}}
                               OPTIONAL,
      -- MUST be present in the first Challenge; MAY be omitted in
      -- any subsequent Challenge in POPODecKeyChallContent (if
      -- omitted, then the owf used in the immediately preceding
      -- Challenge is to be used).
      witness             OCTET STRING,
      -- the result of applying the OWF to a
      -- randomly generated INTEGER, A. (Note that a different
      -- INTEGER MUST be used for each Challenge.)
      challenge           OCTET STRING,
      -- MUST be used for cmp2000(2) popdecc messages and MUST be
      -- the encryption of Rand (using a mechanism depending on the
      -- private key type).
      -- MUST be an empty OCTET STRING for cmp2021(3) popdecc messages.
      -- Note: Using challenge omitting the optional encryptedRand is
      -- bit-compatible to the syntax without adding this optional
      -- field.
      encryptedRand   [0] EnvelopedData OPTIONAL
      -- MUST be omitted for cmp2000(2) popdecc messages.
      -- MUST be used for cmp2021(3) popdecc messages and MUST contain
      -- the encrypted value of Rand using CMS EnvelopedData using the
      -- key management technique depending on the private key type as
      -- defined in Section 5.2.2.
   }

   -- Rand was added in [RFC9480]

   Rand ::= SEQUENCE {
   -- Rand is encrypted involving the public key to form the content of
   -- challenge or encryptedRand in POPODecKeyChallContent
      int                  INTEGER,
      -- the randomly generated INTEGER A (above)
      sender               GeneralName
      -- the sender's name (as included in PKIHeader)
   }

   POPODecKeyRespContent ::= SEQUENCE OF INTEGER
   -- One INTEGER per encryption or key agreement key certification
   -- request (in the same order as these requests appear in
   -- CertReqMessages). The retrieved INTEGER A (above) is returned to
   -- the sender of the corresponding Challenge.

   CertRepMessage ::= SEQUENCE {
       caPubs       [1] SEQUENCE SIZE (1..MAX) OF CMPCertificate
                     OPTIONAL,
       response         SEQUENCE OF CertResponse }

   CertResponse ::= SEQUENCE {
       certReqId           INTEGER,
       -- to match this response with the corresponding request (a value
       -- of -1 is to be used if certReqId is not specified in the
       -- corresponding request, which can only be a p10cr)
       status              PKIStatusInfo,
       certifiedKeyPair    CertifiedKeyPair    OPTIONAL,
       rspInfo             OCTET STRING        OPTIONAL
       -- analogous to the id-regInfo-utf8Pairs string defined
       -- for regInfo in CertReqMsg [RFC4211]
   }

   CertifiedKeyPair ::= SEQUENCE {
       certOrEncCert       CertOrEncCert,
       privateKey      [0] EncryptedKey      OPTIONAL,
       -- See [RFC4211] for comments on encoding.
       -- Changed from EncryptedValue to EncryptedKey as a CHOICE of
       -- EncryptedValue and EnvelopedData due to the changes made in
       -- [RFC9480].
       -- Using the choice EncryptedValue is bit-compatible to the
       -- syntax without this change.
       publicationInfo [1] PKIPublicationInfo  OPTIONAL }

   CertOrEncCert ::= CHOICE {
       certificate     [0] CMPCertificate,
       encryptedCert   [1] EncryptedKey
       -- Changed from Encrypted Value to EncryptedKey as a CHOICE of
       -- EncryptedValue and EnvelopedData due to the changes made in
       -- [RFC9480].
       -- Using the choice EncryptedValue is bit-compatible to the
       -- syntax without this change.
   }

   KeyRecRepContent ::= SEQUENCE {
       status                  PKIStatusInfo,
       newSigCert          [0] CMPCertificate OPTIONAL,
       caCerts             [1] SEQUENCE SIZE (1..MAX) OF
                                        CMPCertificate OPTIONAL,
       keyPairHist         [2] SEQUENCE SIZE (1..MAX) OF
                                        CertifiedKeyPair OPTIONAL }

   RevReqContent ::= SEQUENCE OF RevDetails

   RevDetails ::= SEQUENCE {
       certDetails         CertTemplate,
       -- allows requester to specify as much as they can about
       -- the cert. for which revocation is requested
       -- (e.g., for cases in which serialNumber is not available)
       crlEntryDetails     Extensions{{...}}    OPTIONAL
       -- requested crlEntryExtensions
   }

   RevRepContent ::= SEQUENCE {
       status       SEQUENCE SIZE (1..MAX) OF PKIStatusInfo,
       -- in same order as was sent in RevReqContent
       revCerts [0] SEQUENCE SIZE (1..MAX) OF CertId OPTIONAL,
       -- IDs for which revocation was requested
       -- (same order as status)
       crls     [1] SEQUENCE SIZE (1..MAX) OF CertificateList OPTIONAL
       -- the resulting CRLs (there may be more than one)
   }

   CAKeyUpdAnnContent ::= SEQUENCE {
       oldWithNew   CMPCertificate, -- old pub signed with new priv
       newWithOld   CMPCertificate, -- new pub signed with old priv
       newWithNew   CMPCertificate  -- new pub signed with new priv
   }

   -- CAKeyUpdContent was added in [RFC9810]
   CAKeyUpdContent ::= CHOICE {
       cAKeyUpdAnnV2      CAKeyUpdAnnContent, -- deprecated
       cAKeyUpdAnnV3  [0] RootCaKeyUpdateContent
   }
   -- With cmp2021, the use of CAKeyUpdAnnContent is deprecated, use
   -- RootCaKeyUpdateContent instead.

   CertAnnContent ::= CMPCertificate

   RevAnnContent ::= SEQUENCE {
       status              PKIStatus,
       certId              CertId,
       willBeRevokedAt     GeneralizedTime,
       badSinceDate        GeneralizedTime,
       crlDetails          Extensions{{...}}  OPTIONAL
       -- extra CRL details (e.g., crl number, reason, location, etc.)
   }

   CRLAnnContent ::= SEQUENCE OF CertificateList

   PKIConfirmContent ::= NULL

   NestedMessageContent ::= PKIMessages

   -- CertReqTemplateContent, AttributeTypeAndValue,
   -- ExpandedRegControlSet, id-regCtrl-altCertTemplate,
   -- AltCertTemplate, regCtrl-algId, id-regCtrl-algId, AlgIdCtrl,
   -- regCtrl-rsaKeyLen, id-regCtrl-rsaKeyLen, and RsaKeyLenCtrl
   -- were added in [RFC9480]

   CertReqTemplateContent ::= SEQUENCE {
      certTemplate           CertTemplate,
      -- prefilled certTemplate structure elements
      -- The SubjectPublicKeyInfo field in the certTemplate MUST NOT
      -- be used.
      keySpec                Controls OPTIONAL
      -- MAY be used to specify supported algorithms
      -- Controls  ::= SEQUENCE SIZE (1..MAX) OF AttributeTypeAndValue
      -- as specified in CRMF [RFC4211]
      }

   AttributeTypeAndValue ::= SingleAttribute{{ ... }}

   ExpandedRegControlSet ATTRIBUTE ::= { RegControlSet |
      regCtrl-altCertTemplate | regCtrl-algId | regCtrl-rsaKeyLen, ... }

   regCtrl-altCertTemplate ATTRIBUTE ::=
      { TYPE AltCertTemplate IDENTIFIED BY id-regCtrl-altCertTemplate }

   id-regCtrl-altCertTemplate OBJECT IDENTIFIER ::= { id-regCtrl 7 }

   AltCertTemplate ::= AttributeTypeAndValue
      -- specifies a template for a certificate other than an X.509v3
      -- public key certificate

   regCtrl-algId ATTRIBUTE ::=
      { TYPE AlgIdCtrl IDENTIFIED BY id-regCtrl-algId }

   id-regCtrl-algId OBJECT IDENTIFIER ::= { id-regCtrl 11 }

   AlgIdCtrl ::= AlgorithmIdentifier{ALGORITHM, {...}}
      -- SHALL be used to specify supported algorithms other than RSA

   regCtrl-rsaKeyLen ATTRIBUTE ::=
      { TYPE RsaKeyLenCtrl IDENTIFIED BY id-regCtrl-rsaKeyLen }

   id-regCtrl-rsaKeyLen OBJECT IDENTIFIER ::= { id-regCtrl 12 }

   RsaKeyLenCtrl ::= INTEGER (1..MAX)
      -- SHALL be used to specify supported RSA key lengths

   -- RootCaKeyUpdateContent, CRLSource, and CRLStatus were added in
   -- [RFC9480]

   RootCaKeyUpdateContent ::= SEQUENCE {
      newWithNew       CMPCertificate,
      -- new root CA certificate
      newWithOld   [0] CMPCertificate OPTIONAL,
      -- X.509 certificate containing the new public root CA key
      -- signed with the old private root CA key
      oldWithNew   [1] CMPCertificate OPTIONAL
      -- X.509 certificate containing the old public root CA key
      -- signed with the new private root CA key
      }

   CRLSource ::= CHOICE {
      dpn          [0] DistributionPointName,
      issuer       [1] GeneralNames }

   CRLStatus ::= SEQUENCE {
      source       CRLSource,
      thisUpdate   Time OPTIONAL }

   -- KemCiphertextInfo and KemOtherInfo were added in [RFC9810]

   KemCiphertextInfo ::= SEQUENCE {
      kem              AlgorithmIdentifier{KEM-ALGORITHM, {...}},
      -- AlgId of the KEM algorithm
      ct               OCTET STRING
      -- Ciphertext output from the Encapsulate function
      }

   KemOtherInfo ::= SEQUENCE {
      staticString     PKIFreeText,
      -- MUST be "CMP-KEM"
      transactionID    OCTET STRING,
      -- MUST contain the values from the message previously received
      -- containing the ciphertext (ct) in KemCiphertextInfo
      kemContext   [0] OCTET STRING OPTIONAL
      -- MAY contain additional algorithm-specific context information
     }

   INFO-TYPE-AND-VALUE ::= TYPE-IDENTIFIER

   InfoTypeAndValue ::= SEQUENCE {
       infoType    INFO-TYPE-AND-VALUE.
                       &id({SupportedInfoSet}),
       infoValue   INFO-TYPE-AND-VALUE.
                       &Type({SupportedInfoSet}{@infoType}) }

   SupportedInfoSet INFO-TYPE-AND-VALUE ::= { ... }

   -- Example InfoTypeAndValue contents include, but are not limited
   -- to, the following (uncomment in this ASN.1 module and use as
   -- appropriate for a given environment):
   --
   --   id-it-caProtEncCert    OBJECT IDENTIFIER ::= {id-it 1}
   --      CAProtEncCertValue      ::= CMPCertificate
   --   id-it-signKeyPairTypes OBJECT IDENTIFIER ::= {id-it 2}
   --      SignKeyPairTypesValue   ::= SEQUENCE SIZE (1..MAX) OF
   --                                      AlgorithmIdentifier{{...}}
   --   id-it-encKeyPairTypes  OBJECT IDENTIFIER ::= {id-it 3}
   --      EncKeyPairTypesValue    ::= SEQUENCE SIZE (1..MAX) OF
   --                                      AlgorithmIdentifier{{...}}
   --   id-it-preferredSymmAlg OBJECT IDENTIFIER ::= {id-it 4}
   --      PreferredSymmAlgValue   ::= AlgorithmIdentifier{{...}}
   --   id-it-caKeyUpdateInfo  OBJECT IDENTIFIER ::= {id-it 5}
   --      CAKeyUpdateInfoValue    ::= CAKeyUpdAnnContent
   --      - id-it-caKeyUpdateInfo was deprecated with cmp2021
   --   id-it-currentCRL       OBJECT IDENTIFIER ::= {id-it 6}
   --      CurrentCRLValue         ::= CertificateList
   --   id-it-unsupportedOIDs  OBJECT IDENTIFIER ::= {id-it 7}
   --      UnsupportedOIDsValue    ::= SEQUENCE SIZE (1..MAX) OF
   --                                          OBJECT IDENTIFIER
   --   id-it-keyPairParamReq  OBJECT IDENTIFIER ::= {id-it 10}
   --      KeyPairParamReqValue    ::= OBJECT IDENTIFIER
   --   id-it-keyPairParamRep  OBJECT IDENTIFIER ::= {id-it 11}
   --      KeyPairParamRepValue    ::= AlgorithmIdentifier{{...}}
   --   id-it-revPassphrase    OBJECT IDENTIFIER ::= {id-it 12}
   --      RevPassphraseValue      ::= EncryptedKey
   --      - Changed from Encrypted Value to EncryptedKey as a CHOICE
   --      - of EncryptedValue and EnvelopedData due to the changes
   --      - made in [RFC9480]
   --      - Using the choice EncryptedValue is bit-compatible to
   --      - the syntax without this change
   --   id-it-implicitConfirm  OBJECT IDENTIFIER ::= {id-it 13}
   --      ImplicitConfirmValue    ::= NULL
   --   id-it-confirmWaitTime  OBJECT IDENTIFIER ::= {id-it 14}
   --      ConfirmWaitTimeValue    ::= GeneralizedTime
   --   id-it-origPKIMessage   OBJECT IDENTIFIER ::= {id-it 15}
   --      OrigPKIMessageValue     ::= PKIMessages
   --   id-it-suppLangTags     OBJECT IDENTIFIER ::= {id-it 16}
   --      SuppLangTagsValue       ::= SEQUENCE OF UTF8String
   --   id-it-caCerts          OBJECT IDENTIFIER ::= {id-it 17}
   --      CaCertsValue            ::= SEQUENCE SIZE (1..MAX) OF
   --                                             CMPCertificate
   --      - id-it-caCerts added in [RFC9480]
   --   id-it-rootCaKeyUpdate  OBJECT IDENTIFIER ::= {id-it 18}
   --      RootCaKeyUpdateValue    ::= RootCaKeyUpdateContent
   --      - id-it-rootCaKeyUpdate added in [RFC9480]
   --   id-it-certReqTemplate  OBJECT IDENTIFIER ::= {id-it 19}
   --      CertReqTemplateValue    ::= CertReqTemplateContent
   --      - id-it-certReqTemplate added in [RFC9480]
   --   id-it-rootCaCert       OBJECT IDENTIFIER ::= {id-it 20}
   --      RootCaCertValue         ::= CMPCertificate
   --      - id-it-rootCaCert added in [RFC9480]
   --   id-it-certProfile      OBJECT IDENTIFIER ::= {id-it 21}
   --      CertProfileValue        ::= SEQUENCE SIZE (1..MAX) OF
   --                                                 UTF8String
   --      - id-it-certProfile added in [RFC9480]
   --   id-it-crlStatusList    OBJECT IDENTIFIER ::= {id-it 22}
   --      CRLStatusListValue      ::= SEQUENCE SIZE (1..MAX) OF
   --                                                  CRLStatus
   --      - id-it-crlStatusList added in [RFC9480]
   --   id-it-crls             OBJECT IDENTIFIER ::= {id-it 23}
   --      CRLsValue               ::= SEQUENCE SIZE (1..MAX) OF
   --                                            CertificateList
   --      - id-it-crls added in [RFC9480]
   --   id-it-KemCiphertextInfo    OBJECT IDENTIFIER ::= {id-it 24}
   --      KemCiphertextInfoValue  ::= KemCiphertextInfo
   --      - id-it-KemCiphertextInfo was added in [RFC9810]
   --
   -- where
   --
   --   id-pkix OBJECT IDENTIFIER ::= {
   --      iso(1) identified-organization(3)
   --      dod(6) internet(1) security(5) mechanisms(5) pkix(7)}
   -- and
   --   id-it   OBJECT IDENTIFIER ::= {id-pkix 4}
   --
   --
   -- This construct MAY also be used to define new PKIX Certificate
   -- Management Protocol request and response messages or
   -- general-purpose (e.g., announcement) messages for future needs
   -- or for specific environments.

   GenMsgContent ::= SEQUENCE OF InfoTypeAndValue

   -- May be sent by end entity, RA, or CA (depending on message
   -- content).  The OPTIONAL infoValue parameter of InfoTypeAndValue
   -- will typically be omitted for some of the examples given above.
   -- The receiver is free to ignore any contained OIDs that it
   -- does not recognize.  If sent from end entity to CA, the empty set
   -- indicates that the CA may send
   -- any/all information that it wishes.

   GenRepContent ::= SEQUENCE OF InfoTypeAndValue
   -- The receiver MAY ignore any contained OIDs that it does not
   -- recognize.

   ErrorMsgContent ::= SEQUENCE {
       pKIStatusInfo          PKIStatusInfo,
       errorCode              INTEGER           OPTIONAL,
       -- implementation-specific error codes
       errorDetails           PKIFreeText       OPTIONAL
       -- implementation-specific error details
   }

   CertConfirmContent ::= SEQUENCE OF CertStatus

   CertStatus ::= SEQUENCE {
       certHash    OCTET STRING,
       -- the hash of the certificate, using the same hash algorithm
       -- as is used to create and verify the certificate signature
       certReqId   INTEGER,
       -- to match this confirmation with the corresponding req/rep
       statusInfo  PKIStatusInfo OPTIONAL,
       hashAlg [0] AlgorithmIdentifier{DIGEST-ALGORITHM, {...}} OPTIONAL
       -- the hash algorithm to use for calculating certHash
       -- SHOULD NOT be used in all cases where the AlgorithmIdentifier
       -- of the certificate signature specifies a hash algorithm
      }

   PollReqContent ::= SEQUENCE OF SEQUENCE {
       certReqId              INTEGER }

   PollRepContent ::= SEQUENCE OF SEQUENCE {
       certReqId              INTEGER,
       checkAfter             INTEGER,  -- time in seconds
       reason                 PKIFreeText OPTIONAL }

   --
   -- EKU extension for PKI entities used in CMP
   -- operations, added due to the changes made in [RFC9480]
   -- The EKUs for the CA and RA are reused from CMC, as defined in
   -- [RFC6402]
   --

   -- id-kp-cmcCA OBJECT IDENTIFIER ::= { id-kp 27 }
   -- id-kp-cmcRA OBJECT IDENTIFIER ::= { id-kp 28 }
   id-kp-cmKGA OBJECT IDENTIFIER ::= { id-kp 32 }

   END
