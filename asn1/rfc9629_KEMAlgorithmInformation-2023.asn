KEMAlgorithmInformation-2023
       { iso(1) identified-organization(3) dod(6) internet(1)
         security(5) mechanisms(5) pkix(7) id-mod(0)
             id-mod-kemAlgorithmInformation-2023(109) }

     DEFINITIONS EXPLICIT TAGS ::=
     BEGIN
     -- EXPORTS ALL;
     IMPORTS
       ParamOptions, PUBLIC-KEY, SMIME-CAPS
       FROM AlgorithmInformation-2009
         { iso(1) identified-organization(3) dod(6) internet(1)
           security(5) mechanisms(5) pkix(7) id-mod(0)
           id-mod-algorithmInformation-02(58) } ;

     -- KEM-ALGORITHM
     --
     -- Describes the basic properties of a KEM algorithm
     --
     -- Suggested prefix for KEM algorithm objects is: kema-
     --
     --  &id - contains the OID identifying the KEM algorithm
     --  &Value - if present, contains a type definition for the kemct;
     --               if absent, implies that no ASN.1 encoding is
     --               performed on the kemct value
     --  &Params - if present, contains the type for the algorithm
     --               parameters; if absent, implies no parameters
     --  &paramPresence - parameter presence requirement
     --  &PublicKeySet - specifies which public keys are used with
     --               this algorithm
     --  &Ukm - if absent, type for user keying material
     --  &ukmPresence - specifies the requirements to define the UKM
     --               field
     --  &smimeCaps - contains the object describing how the S/MIME
     --               capabilities are presented.
     --
     -- Example:
     -- kema-kem-rsa KEM-ALGORITHM ::= {
     --    IDENTIFIER id-kem-rsa
     --    PARAMS TYPE RsaKemParameters ARE optional
     --    PUBLIC-KEYS { pk-rsa | pk-rsa-kem }
     --    UKM ARE optional
     --    SMIME-CAPS { TYPE GenericHybridParameters
     --        IDENTIFIED BY id-rsa-kem }
     -- }

     KEM-ALGORITHM ::= CLASS {
       &id             OBJECT IDENTIFIER UNIQUE,
       &Value          OPTIONAL,
       &Params         OPTIONAL,
       &paramPresence  ParamOptions DEFAULT absent,
       &PublicKeySet   PUBLIC-KEY OPTIONAL,
       &Ukm            OPTIONAL,
       &ukmPresence    ParamOptions DEFAULT absent,
       &smimeCaps      SMIME-CAPS OPTIONAL
     } WITH SYNTAX {
       IDENTIFIER &id
       [VALUE &Value]
       [PARAMS [TYPE &Params] ARE &paramPresence]
       [PUBLIC-KEYS &PublicKeySet]
       [UKM [TYPE &Ukm] ARE &ukmPresence]
       [SMIME-CAPS &smimeCaps]
     }

     END
