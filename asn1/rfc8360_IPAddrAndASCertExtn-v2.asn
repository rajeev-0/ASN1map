IPAddrAndASCertExtn-v2 { iso(1) identified-organization(3) dod(6)
      internet(1) security(5) mechanisms(5) pkix(7) mod(0)
      id-mod-ip-addr-and-as-ident-v2(90) }

   DEFINITIONS EXPLICIT TAGS ::=

   BEGIN

   -- EXPORTS ALL --

   IMPORTS

   -- PKIX specific OIDs and arcs --

   id-pe FROM PKIX1Explicit88 { iso(1) identified-organization(3)
        dod(6) internet(1) security(5) mechanisms(5) pkix(7)
        id-mod(0) id-pkix1-explicit(18) }

   -- IP Address Block and AS Identifiers Syntax --

   IPAddrBlocks, ASIdentifiers FROM  IPAddrAndASCertExtn { iso(1)
      identified-organization(3) dod(6) internet(1) security(5)
      mechanisms(5) pkix(7) mod(0) id-mod-ip-addr-and-as-ident(30) }
   ;

   -- Validation Reconsidered IP Address Delegation Extension OID --

   id-pe-ipAddrBlocks-v2  OBJECT IDENTIFIER ::= { id-pe 28 }

   -- Validation Reconsidered IP Address Delegation Extension Syntax --
   -- Syntax is imported from RFC 3779 --

   -- Validation Reconsidered Autonomous System Identifier --
   --     Delegation Extension OID                         --

   id-pe-autonomousSysIds-v2  OBJECT IDENTIFIER ::= { id-pe 29 }

   -- Validation Reconsidered Autonomous System Identifier --
   --     Delegation Extension Syntax                      --

   -- Syntax is imported from RFC 3779 --

   END
