PSKCAttributesModule
     { iso(1) member-body(2) us(840) rsadsi(113549) pkcs(1) pkcs-9(9)
       smime(16) modules(0) id-mod-pskcAttributesModule(53) }

   DEFINITIONS IMPLICIT TAGS ::=

   BEGIN

   -- EXPORTS ALL

   IMPORTS

   -- From New PKIX ASN.1 [RFC5912]

   ATTRIBUTE
     FROM PKIX-CommonTypes-2009
      { iso(1) identified-organization(3) dod(6) internet(1)
        security(5) mechanisms(5) pkix(7) id-mod(0)
        id-mod-pkixCommon-02(57) }









   -- From BinaryTime [RFC6019]

   BinaryTime
     FROM BinarySigningTimeModule
       { iso(1) member-body(2) us(840) rsadsi(113549) pkcs(1) pkcs-9(9)
         smime(16) modules(0) id-mod-binarySigningTime(27) }

   -- From New SMIME ASN.1 [RFC5911]

   id-smime
     FROM SecureMimeMessageV3dot1-2009
       { iso(1) member-body(2) us(840) rsadsi(113549) pkcs(1) pkcs-9(9)
         smime(16) modules(0) id-mod-msg-v3dot1-02(39) }

   ;

   --
   -- PSKC Attributes OIDs are taken from the SMIME Arc.
   --

   id-pskc OBJECT IDENTIFIER ::= { id-smime 12 }

   --
   -- Merge SKeyPKGAttributes to the set of attributes for sKeyPkgAttrs
   --

   SKeyPkgAttributes ATTRIBUTE ::= {
     at-pskc-manufacturer | at-pskc-serialNo | at-pskc-model |
     at-pskc-issueNo | at-pskc-deviceBinding |
     at-pskc-deviceStartDate | at-pskc-deviceExpiryDate |
     at-pskc-moduleId | at-pskc-deviceUserId, ... }

   --
   -- Merge SKeyAttributes to the set of attributes for sKeyAttrs
   --

   SKeyAttributes ATTRIBUTE ::= {
     at-pskc-keyId | at-pskc-algorithm | at-pskc-issuer |
     at-pskc-keyProfileId | at-pskc-keyReference |
     at-pskc-friendlyName | at-pskc-algorithmParameters |
     at-pskc-counter | at-pskc-time | at-pskc-timeInterval |
     at-pskc-timeDrift | at-pskc-valueMAC | at-pskc-keyUserId  |
     at-pskc-keyStartDate | at-pskc-keyExpiryDate |
     at-pskc-numberOfTransactions | at-pskc-keyUsage |
     at-pskc-pinPolicy, ... }

   at-pskc-manufacturer ATTRIBUTE ::= {
     TYPE UTF8String IDENTIFIED BY id-pskc-manufacturer }






   id-pskc-manufacturer OBJECT IDENTIFIER ::= { id-pskc 1 }

   at-pskc-serialNo ATTRIBUTE ::= {
     TYPE UTF8String IDENTIFIED BY id-pskc-serialNo }

   id-pskc-serialNo OBJECT IDENTIFIER ::= { id-pskc 2 }

   at-pskc-model ATTRIBUTE ::= {
     TYPE UTF8String IDENTIFIED BY id-pskc-model }

   id-pskc-model OBJECT IDENTIFIER ::= { id-pskc 3 }

   at-pskc-issueNo ATTRIBUTE ::= {
     TYPE UTF8String IDENTIFIED BY id-pskc-issueNo }

   id-pskc-issueNo OBJECT IDENTIFIER ::= { id-pskc 4 }

   at-pskc-deviceBinding ATTRIBUTE ::= {
     TYPE UTF8String IDENTIFIED BY id-pskc-deviceBinding }

   id-pskc-deviceBinding OBJECT IDENTIFIER ::= { id-pskc 5 }

   at-pskc-deviceStartDate ATTRIBUTE ::= {
     TYPE GeneralizedTime IDENTIFIED BY id-pskc-deviceStartDate }

   id-pskc-deviceStartDate OBJECT IDENTIFIER ::= { id-pskc 6 }

   at-pskc-deviceExpiryDate ATTRIBUTE ::= {
     TYPE GeneralizedTime IDENTIFIED BY id-pskc-deviceExpiryDate }

   id-pskc-deviceExpiryDate OBJECT IDENTIFIER ::= { id-pskc 7 }

   at-pskc-moduleId ATTRIBUTE ::= {
     TYPE UTF8String IDENTIFIED BY id-pskc-moduleId }

   id-pskc-moduleId OBJECT IDENTIFIER ::= { id-pskc 8 }

   at-pskc-deviceUserId ATTRIBUTE ::= {
     TYPE UTF8String IDENTIFIED BY id-pskc-deviceUserId }

   id-pskc-deviceUserId OBJECT IDENTIFIER ::= { id-pskc 26 }

   at-pskc-keyId ATTRIBUTE ::= {
     TYPE UTF8String IDENTIFIED BY id-pskc-keyId }

   id-pskc-keyId OBJECT IDENTIFIER ::= { id-pskc 9 }








   at-pskc-algorithm ATTRIBUTE ::= {
     TYPE UTF8String IDENTIFIED BY id-pskc-algorithm }

   id-pskc-algorithm OBJECT IDENTIFIER ::= { id-pskc 10 }

   at-pskc-issuer ATTRIBUTE ::= {
     TYPE UTF8String IDENTIFIED BY id-pskc-issuer }

   id-pskc-issuer OBJECT IDENTIFIER ::= { id-pskc 11 }

   at-pskc-keyProfileId ATTRIBUTE ::= {
     TYPE UTF8String IDENTIFIED BY id-pskc-keyProfileId }

   id-pskc-keyProfileId OBJECT IDENTIFIER ::= { id-pskc 12 }

   at-pskc-keyReference ATTRIBUTE ::= {
     TYPE UTF8String IDENTIFIED BY id-pskc-keyReference }

   id-pskc-keyReference OBJECT IDENTIFIER ::= { id-pskc 13 }

   at-pskc-friendlyName ATTRIBUTE ::= {
     TYPE FriendlyName IDENTIFIED BY id-pskc-friendlyName }

   id-pskc-friendlyName OBJECT IDENTIFIER ::= { id-pskc 14 }

   FriendlyName ::= SEQUENCE {
     friendlyName        UTF8String,
     friendlyNameLangTag UTF8String OPTIONAL }

   at-pskc-algorithmParameters ATTRIBUTE ::= {
     TYPE PSKCAlgorithmParameters
     IDENTIFIED BY id-pskc-algorithmParameters }

   id-pskc-algorithmParameters OBJECT IDENTIFIER ::= { id-pskc 15 }

   PSKCAlgorithmParameters ::= CHOICE {
     suite                UTF8String,
     challengeFormat  [0] ChallengeFormat,
     responseFormat   [1] ResponseFormat,
     ... }

   ChallengeFormat ::= SEQUENCE {
     encoding    Encoding,
     checkDigit  BOOLEAN DEFAULT FALSE,
     min         INTEGER (0..MAX),
     max         INTEGER (0..MAX),
     ... }







   Encoding ::= UTF8String ("DECIMAL" | "HEXADECIMAL" |
                "ALPHANUMERIC" | "BASE64" | "BINARY" )

   ResponseFormat ::= SEQUENCE {
     encoding     Encoding,
     length       INTEGER (0..MAX),
     checkDigit   BOOLEAN DEFAULT FALSE,
     ... }

   at-pskc-counter ATTRIBUTE ::= {
     TYPE INTEGER (0..MAX) IDENTIFIED BY id-pskc-counter }

   id-pskc-counter OBJECT IDENTIFIER ::= { id-pskc 16 }

   at-pskc-time ATTRIBUTE ::= {
     TYPE BinaryTime IDENTIFIED BY id-pskc-time }

   id-pskc-time OBJECT IDENTIFIER ::= { id-pskc 17 }

   at-pskc-timeInterval ATTRIBUTE ::= {
     TYPE INTEGER (0..MAX) IDENTIFIED BY id-pskc-timeInterval }

   id-pskc-timeInterval OBJECT IDENTIFIER ::= { id-pskc 18 }

   at-pskc-timeDrift ATTRIBUTE ::= {
     TYPE INTEGER (0..MAX) IDENTIFIED BY id-pskc-timeDrift }

   id-pskc-timeDrift OBJECT IDENTIFIER ::= { id-pskc 19 }

   at-pskc-valueMAC ATTRIBUTE ::= {
     TYPE ValueMac IDENTIFIED BY id-pskc-valueMAC }

   id-pskc-valueMAC OBJECT IDENTIFIER ::= { id-pskc 20 }

   ValueMac ::= SEQUENCE {
     macAlgorithm UTF8String,
     mac          UTF8String }

   at-pskc-keyUserId ATTRIBUTE ::= {
     TYPE UTF8String IDENTIFIED BY id-pskc-keyUserId }

   id-pskc-keyUserId OBJECT IDENTIFIER ::= { id-pskc 27 }

   at-pskc-keyStartDate ATTRIBUTE ::= {
     TYPE GeneralizedTime IDENTIFIED BY id-pskc-keyStartDate }

   id-pskc-keyStartDate OBJECT IDENTIFIER ::= { id-pskc 21 }







   at-pskc-keyExpiryDate ATTRIBUTE ::= {
     TYPE GeneralizedTime IDENTIFIED BY id-pskc-keyExpiryDate }

   id-pskc-keyExpiryDate OBJECT IDENTIFIER ::= { id-pskc 22 }

   at-pskc-numberOfTransactions ATTRIBUTE ::= {
     TYPE INTEGER (0..MAX) IDENTIFIED BY id-pskc-numberOfTransactions }

   id-pskc-numberOfTransactions OBJECT IDENTIFIER ::= { id-pskc 23 }

   at-pskc-keyUsage ATTRIBUTE ::= {
     TYPE PSKCKeyUsages IDENTIFIED BY id-pskc-keyUsages }

   id-pskc-keyUsages OBJECT IDENTIFIER ::= { id-pskc 24 }

   PSKCKeyUsages ::= SEQUENCE OF PSKCKeyUsage

   PSKCKeyUsage ::= UTF8String ("OTP" | "CR" | "Encrypt" |
                    "Integrity" | "Verify" | "Unlock" | "Decrypt" |
                    "KeyWrap" | "Unwrap" | "Derive" | "Generate")

   at-pskc-pinPolicy ATTRIBUTE ::= {
     TYPE PINPolicy IDENTIFIED BY id-pskc-pinPolicy }

   id-pskc-pinPolicy OBJECT IDENTIFIER ::= { id-pskc 25 }

   PINPolicy ::= SEQUENCE {
     pinKeyId          [0] UTF8String OPTIONAL,
     pinUsageMode      [1] PINUsageMode,
     maxFailedAttempts [2] INTEGER (0..MAX) OPTIONAL,
     minLength         [3] INTEGER (0..MAX) OPTIONAL,
     maxLength         [4] INTEGER (0..MAX) OPTIONAL,
     pinEncoding       [5] Encoding OPTIONAL }

   PINUsageMode ::= UTF8String ("Local" | "Prepend" | "Append"|
                    "Algorithmic")

   END
